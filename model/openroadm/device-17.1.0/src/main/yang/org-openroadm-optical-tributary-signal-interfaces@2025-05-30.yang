module org-openroadm-optical-tributary-signal-interfaces {
  namespace "http://org/openroadm/optical-channel-tributary-signal-interfaces";
  prefix org-openroadm-optical-tributary-signal-interfaces;

  import org-openroadm-common-link-types {
    prefix org-openroadm-common-link-types;
    revision-date 2024-12-13;
  }
  import org-openroadm-common-optical-channel-types {
    prefix org-openroadm-common-optical-channel-types;
    revision-date 2025-03-28;
  }
  import org-openroadm-common-types {
    prefix org-openroadm-common-types;
    revision-date 2025-05-30;
  }
  import org-openroadm-optical-operational-interfaces {
    prefix org-openroadm-optical-operational-interfaces;
    revision-date 2025-03-28;
  }
  import org-openroadm-device {
    prefix org-openroadm-device;
    revision-date 2025-05-30;
  }
  import org-openroadm-interfaces {
    prefix openROADM-if;
    revision-date 2022-09-30;
  }
  import org-openroadm-otn-common-types {
    prefix org-openroadm-otn-common-types;
    revision-date 2025-05-30;
  }
  import org-openroadm-common-pluggable-types {
    prefix org-openroadm-common-pluggable-types;
    revision-date 2025-05-30;
  }
  import org-openroadm-otn-common {
    prefix org-openroadm-otn-common;
    revision-date 2025-05-30;
  }

  organization
    "Open ROADM MSA";
  contact
    "OpenROADM.org";
  description
    "YANG definitions for device optical tributary signal interfaces.

     Copyright of the Members of the Open ROADM MSA Agreement dated (c) 2018,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Also contains code components extracted from IETF Interfaces.  These code components
     are copyrighted and licensed as follows:

     Copyright (c) 2016 IETF Trust and the persons identified as the document authors.
     All rights reserved.

     This document is subject to BCP 78 and the IETF Trust’s Legal Provisions Relating
     to IETF Documents (http://trustee.ietf.org/license-info) in effect on the date of
     publication of this document. Please review these documents carefully, as they
     describe your rights and restrictions with respect to this document. Code Components
     extracted from this document must include Simplified BSD License text as described in
     Section 4.e of the Trust Legal Provisions and are provided without warranty as
     described in the Simplified BSD License.";

  revision 2025-05-30 {
    description
      "Version 17.1.0";
  }
  revision 2025-03-28 {
    description
      "Version 17.0";
  }
  revision 2024-12-13 {
    description
      "Version 16.1";
  }
  revision 2024-09-27 {
    description
      "Version 16.0";
  }
  revision 2024-05-31 {
    description
      "Version 15.1";
  }
  revision 2024-03-29 {
    description
      "Version 15.0";
  }
  revision 2023-12-08 {
    description
      "Version 14.1";
  }
  revision 2023-09-29 {
    description
      "Version 14.0";
  }
  revision 2023-05-26 {
    description
      "Version 13.1";
  }
  revision 2023-03-31 {
    description
      "Version 13.0";
  }
  revision 2022-12-09 {
    description
      "Version 12.1";
  }
  revision 2022-09-30 {
    description
      "Version 12.0";
  }
  revision 2022-05-27 {
    description
      "Version 11.1";
  }
  revision 2022-03-25 {
    description
      "Version 11.0";
  }
  revision 2021-12-10 {
    description
      "Version 10.1";
  }
  revision 2021-09-24 {
    description
      "Version 10.0";
  }
  revision 2021-05-28 {
    description
      "Version 9.1";
  }
  revision 2021-03-26 {
    description
      "Version 9.0";
  }
  revision 2020-12-11 {
    description
      "Version 8.1";
  }
  revision 2020-09-25 {
    description
      "Version 8.0";
  }
  revision 2020-05-29 {
    description
      "Version 7.1.0";
  }
  revision 2020-03-27 {
    description
      "Version 7.0.0";
  }
  revision 2019-11-29 {
    description
      "Version 6.1.0";
  }
  revision 2019-09-27 {
    description
      "Version 6.0.0";
  }
  revision 2019-05-31 {
    description
      "Version 5.1.0";
  }
  revision 2019-03-29 {
    description
      "Version 5.0.0";
  }
  revision 2018-11-30 {
    description
      "Version 4.1.0";
  }
  revision 2018-05-30 {
    description
      "Version 3.1.0";
  }
  revision 2018-03-30 {
    description
      "Version 3.0.0";
  }

  grouping otsi-attributes {
    description
      "OTSi attributes group";
    leaf provision-mode {
      type org-openroadm-common-optical-channel-types:provision-mode-type;
      default "explicit";
      description
        "The provision-mode specified by the controller. Default to 'explicit' (ie, the set of optical parameter specified in MSA Optical Spec).
         The 'profile' provision-mode is introduced in MSA 5.0 to support the bookended xponder application";
    }
    leaf otsi-rate {
      when "../provision-mode = 'explicit' or ../provision-mode = 'media-id'";
      type identityref {
        base org-openroadm-common-optical-channel-types:otsi-rate-identity;
      }
      description
        "OTSi rate";
    }
    leaf otsi-member-id {
      type uint16;
      description
        "The member ID to uniquely identify each member in an OTSi group and the order of each member in the group.  For each group, system shall support non-consecutive member IDs.  User shall not set up two members with the same member ID.  Similar to FlexO PHY-ID in the FlexO Group (PID in G.709.1/3)";
    }
    leaf frequency {
      type org-openroadm-common-optical-channel-types:frequency-THz;
      description
        "Center Frequency in THz.";
    }
    leaf width {
      when "../provision-mode = 'explicit'";
      type org-openroadm-common-optical-channel-types:frequency-GHz;
      config false;
      description
        "Frequency width in GHz.";
    }
    uses org-openroadm-common-types:enable-laser;
    leaf modulation-format {
      when "../provision-mode = 'explicit'";
      type org-openroadm-common-optical-channel-types:modulation-format;
      description
        "Modulation format";
    }
    leaf transmit-power {
      type org-openroadm-common-link-types:power-dBm;
      description
        "The target transmit power for this channel. When set, the xponder will work to ensure that port-current-power reaches this level. Applicable only to channel on top of xpdr-network port";
    }
    uses org-openroadm-common-types:fec-grouping {
      when "provision-mode = 'explicit'";
      description
        "OTSi FEC / Forward Error Correction";
    }
    uses org-openroadm-common-pluggable-types:cmis-media-id {
      when "/org-openroadm-device:org-openroadm-device/org-openroadm-device:interface/org-openroadm-optical-tributary-signal-interfaces:otsi/provision-mode = 'media-id'";
      description
        "media-interface-id and associated-oui";
    }
    leaf optical-operational-mode {
      when "../provision-mode = 'profile'";
      type string;
      description
        "Optical-operational-mode sets the xponder settings based on one of the operational mode capabilities as published by the device.  This attribute is mandatory when the provision-mode is set to profile.";
    }
    container operational-mode-params {
      when "../provision-mode = 'profile'";
      config false;
      description
        "The container containing the optical parameters for the specified operational mode";
      uses org-openroadm-optical-operational-interfaces:optical-operational-modes-grp-attr;
    }
    leaf supported-group-if {
      type leafref {
        path "/org-openroadm-device:org-openroadm-device/org-openroadm-device:interface/org-openroadm-device:name";
      }
      config false;
      description
        "OTSiG or FlexO-group interface name.";
    }
    container flexo {
      presence "Explicit assigment for flexo container";
      description
        "Flexo presence container";
      reference
        "Applicable to Ethernet optimized non-OTN FlexO-xe (G.709.1 Amd4 draft 2023-03), and
         OTN based mapping FlexO-x (G.709 2020-12)";
      leaf foic-type {
        type identityref {
          base org-openroadm-common-optical-channel-types:foic-identity;
        }
        description
          "Assigned flexo instance type. FOIC type is not specified when the provision-mode is profile or media-id";
      }
      leaf-list iid {
        type uint8;
        min-elements 1;
        ordered-by user;
        description
          "A list of FlexO instance identification (G.709.1 clause 9.2.3)";
      }
      leaf payload-id {
        type org-openroadm-otn-common-types:flexo-payload-type-def;
        description
          "Payload type PT (Section 9.2.6.2, G.709.1 2020-12). For example, applicable to OIF 800ZR (0x40) (ITU-T)";
      }
      leaf flexo-mode {
        type string;
        description
          "Generic line mapping application:
           'flexo-x' for OTN mapped FlexO-x,
           'flexo-xe' for Ethernet optimized FlexO-xe,
           'oifzr' OIF (eg, 400ZR, 800ZR),
           'openzr+' for Industry OpenZR+ MSA (eg, 400ZR+)";
      }
      leaf-list accepted-group-id {
        type uint32;
        config false;
        description
          "AcGID[1]..AcGID[n] on a per FlexO instance basis (G.798 2019-12, Figure 15-10 FlexO-n/OTUCn_A_Sk processes)";
      }
      leaf-list accepted-iid {
        type uint8;
        config false;
        description
          "AcIID[1]..AcIID[n] on a per FlexO instance basis (G.798 2019-12, Figure 15-10 FlexO-n/OTUCn_A_Sk processes)";
      }
      leaf-list accepted-payload-id {
        type org-openroadm-otn-common-types:flexo-payload-type-def;
        config false;
        description
          "FlexO payload type extracted from PT overhead (G.798 15.3.5.2
           (FlexO-n/OTUCni_A_Sk)(2021-01))";
      }
      uses org-openroadm-otn-common:trail-trace;
    }
  }
  grouping otsi-container {
    description
      "OTSI container group";
    container otsi {
      description
        "OTSi container";
      uses org-openroadm-optical-tributary-signal-interfaces:otsi-attributes;
    }
  }
  augment "/org-openroadm-device:org-openroadm-device/org-openroadm-device:interface" {
    when "org-openroadm-device:type = 'openROADM-if:otsi'";
    description
      "augment for otsi";
    uses org-openroadm-optical-tributary-signal-interfaces:otsi-container;
  }
}
