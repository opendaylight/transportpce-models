module openconfig-platform-linecard {

  yang-version "1";

  // namespace
  namespace "http://openconfig.net/yang/platform/linecard";

  prefix "oc-linecard";

  import openconfig-platform { prefix oc-platform; revision-date 2025-07-15; }
  import openconfig-extensions { prefix oc-ext; revision-date 2024-09-19; }


  // meta
  organization "OpenConfig working group";

  contact
    "OpenConfig working group
    www.openconfig.net";

  description
    "This module defines data related to LINECARD components in
    the openconfig-platform model";

oc-ext:openconfig-version "1.2.0";

   revision "2024-04-12" {
    description
      "Add install-position, install-component and deprecate location and
      slot-id.";
    reference "1.2.0";
  }

  revision "2023-02-13" {
    description
      "Renamed platform-utilization-top to platform-resource-utilization-top.";
    reference "1.1.0";
  }

  revision "2022-07-28" {
    description
      "Remove leaf power-admin-state and use a common definition
      instead.";
    reference "1.0.0";
  }

  revision "2022-04-21" {
    description
      "Add platform utilization to linecard.";
    reference "0.2.0";
  }

  revision "2020-05-10" {
    description
      "Remove when statement that references read-only entity from
      a read-write context.";
    reference "0.1.2";
  }

  revision "2018-11-21" {
    description
      "Add OpenConfig module metadata extensions.";
    reference "0.1.1";
  }

  revision "2017-08-03" {
    description
      "Initial revision";
    reference "0.1.0";
  }

  // OpenConfig specific extensions for module metadata.
  oc-ext:regexp-posix;
  oc-ext:catalog-organization "openconfig";
  oc-ext:origin "openconfig";

  // extension statements

  // feature statements

  // identity statements

  // typedef statements

  // grouping statements

  grouping linecard-config {
    description
      "Configuration data for linecard components";

    uses oc-platform:component-power-management;
  }

  grouping linecard-state {
    description
      "Operational state data for linecard components";

    leaf slot-id {
      status deprecated;
      type string;
      description
        "Identifier for the slot or chassis position in which the
        linecard is installed.

        This leaf is deprecated and will be replaced by install-position
        and install-component leaves in a future major revision of this
        model.";
    }
  }

  grouping linecard-top {
    description
      "Top-level grouping for linecard data";

    container linecard {
      description
        "Top-level container for linecard data";

      container config {
        description
          "Configuration data for linecards";

        uses linecard-config;
      }

      container state {

        config false;

        description
          "Operational state data for linecards";

        uses linecard-config;
        uses linecard-state;
      }
      uses oc-platform:platform-resource-utilization-top;
    }
  }

  // data definition statements

  // augment statements

  augment "/oc-platform:components/oc-platform:component" {
    description
      "Adding linecard data to physical inventory. This subtree
      is only valid when the type of the component is LINECARD.";

    uses linecard-top;
  }

  // rpc statements

  // notification statements

}
