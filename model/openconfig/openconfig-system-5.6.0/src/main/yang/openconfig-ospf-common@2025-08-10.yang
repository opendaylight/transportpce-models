submodule openconfig-ospf-common {

  belongs-to openconfig-ospf {
    prefix "oc-ospf";
  }

  import openconfig-extensions { prefix "oc-ext"; revision-date 2024-09-19; }

  // meta
  organization "OpenConfig working group";

  contact
    "OpenConfig working group
    www.openconfig.net";

  description
    "This submodule provides common OSPF configuration and operational
    state parameters that are shared across multiple contexts";

  oc-ext:openconfig-version "0.1.1";

  revision "2025-08-10" {
    description
      "Removed duplicate import and updated prefixes in openconfig-ospf-area";
    reference "0.1.1";
  }
  revision "2025-02-13" {
    description
      "Initial revision";
    reference "0.0.1";
  }

  grouping ospf-common-timers {
    description
      "Common definition of the type of timers that the OSPF implementation
      uses";

    leaf timer-type {
      type enumeration {
        enum LINEAR_BACKOFF {
          description
            "The backoff used by the OSPF implementation is linear, such that
            a common delay is added following each event.";
        }
        enum EXPONENTIAL_BACKOFF {
          description
            "The backoff used by the OSPF implementation is exponential, such
            that the delay added following each event increases.";
        }
      }
      description
        "The timer mode that is utilised by the implementation.";
    }
  }

}
